module wifi {
  namespace "http://tail-f.com/ns/example/wifi";
  prefix wifi;

  import ietf-inet-types {
    prefix inet;
  }
  import tailf-common {
    prefix tailf;
  }

	typedef IfType {
		type enumeration {
			enum dynamic;
			enum static;
		}
	}

	container scan_results {
		config false;
		tailf:callpoint wifi_scan_results;
		list result {
			key "bssid";

			leaf bssid {
				type string;
			}
			leaf frequency {
				type int32;
			}
			leaf signal_level {
				type int32;
			}
			leaf flags {
				type string;
			}
			leaf ssid {
				type string;
			}
		}
	}

  list wifi {
		key port;

		leaf port {
			type int32;
		}

    leaf mode {
      type enumeration {
        enum mode_station;
        enum mode_access_point;
        enum mode_off;
      }
    }

    container station {
      leaf ssid {
        type string;
      }
      leaf psk {
        type string;
      }
			leaf ip-address-src {
				type IfType;
				default dynamic;
			}
    }

    container access_point {
      leaf ssid {
        type string;
      }
      leaf psk {
        type string;
      }
    }

		tailf:action connect {
			tailf:actionpoint connect-point;
			input {
				list access_point {
					key ssid;

					leaf ssid {
						type leafref {
							path "/scan_results/result/ssid";
						}
					}
				}
				leaf psk {
					type string;
				}
			}
			output {
				leaf status {
					type string;
					mandatory true;
				}
			}
		}
  }
}
